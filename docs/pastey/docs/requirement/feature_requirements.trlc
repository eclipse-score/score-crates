/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package PasteyFeatReq

import ScoreReq
import RustCrateSysReq

ScoreReq.FeatReq FEAT_PASTEY_001 {
    description = "The pastey crate shall provide compile-time token manipulation capabilities for procedural macro expansion in Rust applications."
    safety = ScoreReq.Asil.B
    derived_from = [RustCrateSysReq.ASR_RUST_CRATE@1]
    version = 1
}
