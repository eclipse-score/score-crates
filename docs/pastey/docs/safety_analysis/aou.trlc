/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package PasteyAoU

import ScoreReq

ScoreReq.AoU PasteyRustCompilerCertified {
    description = "The Rust compiler used to build the pastey crate shall be safety certified up to ASIL B."
    safety = ScoreReq.Asil.B
    version = 1
    note = "Safety-critical software development requires a qualified toolchain to ensure compiler-generated code meets functional safety requirements"
    mitigates = "UncertifiedRustCompiler"
}
