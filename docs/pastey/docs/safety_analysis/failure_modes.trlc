/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package PasteyFailureModes

import ScoreReq

ScoreReq.FailureMode UncertifiedRustCompiler {
    guideword = ScoreReq.GuideWord.UnintendedFunction
    description = "The pastey crate is built with a Rust compiler that is not safety certified up to ASIL B, potentially producing code that does not meet functional safety requirements."
    failureeffect = "Compiler-generated code may contain defects that violate functional safety requirements, potentially leading to unsafe system behavior."
    safety = ScoreReq.Asil.B
    version = 1
    potentialcause = "A non-qualified Rust compiler toolchain is used during the build of safety-critical software that incorporates the pastey crate."
    interface = "pastey_pub.paste_macro"
}
